Attribute VB_Name = "Rewrite"
Public Sub StoreLastKnownGoodValues()

    Dim oItemLibs As ItemTypeLibraries
    Dim oItemLib As itemTypelibrary
    Dim oDgn As designFile
    Dim oItem As ItemType
    Dim LKGProperty As ItemTypeProperty
    Do
        Set oItemLib = ActiveDesignFile.ItemTypeLibraries.Find("*", oItemLib)
        If oItemLib Is Nothing Then Exit Do
        Do
            Set oItem = oItemLib.Find("*", oItem)
            If oItem Is Nothing Then Exit Do
            Set LKGProperty = oItem.AddProperty("RepairLKG", ItemPropertyTypeBoolean)
            oItemLib.Write
            oItem.RemoveProperty (LKGProperty.GetPropId())
            oItemLib.Write
        Loop
    Loop
    
End Sub
